-- Copyright 2018 PayTrace, Inc.
-- 
-- Licensed under the Apache License, Version 2.0 (the "License");
-- you may not use this file except in compliance with the License.
-- You may obtain a copy of the License at
-- 
--     http://www.apache.org/licenses/LICENSE-2.0
-- 
-- Unless required by applicable law or agreed to in writing, software
-- distributed under the License is distributed on an "AS IS" BASIS,
-- WITHOUT WARRANTIES OR CONDITIONS OF ANY KIND, either express or implied.
-- See the License for the specific language governing permissions and
-- limitations under the License.

JSON-module DEFINITIONS ::= -- For encoding JSON-ic values with ASN.1
BEGIN

EXPORTS JSONValue, JSONObject, KeyValuePair;

JSONObject ::= SET OF KeyValuePair

JSONValue ::= CHOICE {
  nullval NULL,
  strval UTF8String,
  numval REAL,
  boolval BOOLEAN,
  objval JSONObject,
  arrval SEQUENCE OF JSONValue
}

KeyValuePair ::= [APPLICATION 1] IMPLICIT SEQUENCE {
  key UTF8String,
  value JSONValue
}

END
